module integrationtest {

  namespace "http://brewerslabng.mellon-collie.net/yang/integrationtest";
  prefix "integrationtest";
  yang-version 1.1;


  import crux { prefix crux; }
  import testchild { prefix testchild; }
  import secondmodule { prefix second; }
  import ietf-inet-types { prefix inet; }
  import scaling { prefix scale; }

  extension hide {
    description "Hide this element - defined in integration test";
    argument boolean {
      yin-element true;
    }
  }


  typedef date {
    description "date format YYYY-MM-DD - this isn't super precise validation";
    type string {
      pattern "[1-2][0-9][0-9][0-9]-[0-1][0-9]-[0-3][0-9]" {
        error-message "Date format must be YYYY-MM-DD";
      }
    }
  }

  typedef countries {
    type enumeration {
      enum GB;
      enum DK;
      enum DE;
      enum FR;
      enum NL;
    }
    default GB;
  }

  typedef locations {
    type enumeration {
      enum Islington;
      enum Camden;
      enum Hackney;
      enum Brixton;
      enum SOHO;
      enum Dalston;
      enum Kensington;
      enum Shoreditch;
      enum Clapham;
      enum "Charring Cross";
      enum "Shepherds Bush";
      enum "Kings Cross";
      enum Southend;
      enum Glasgow;
      enum Newcastle;
      enum Sheffield;
      enum Oxford;
      enum Norwich;
      enum Cleethorpes;
      enum Rotherham;
      enum Nottingham;
      enum Cambridge;
      enum Manchester;
      enum Reading;
      enum Colchester;
      enum Berlin;
      enum Eindhoven;
      enum Hannover;
      enum Paris;
      enum Copenhagen;
      enum Amsterdam;
    }
  }

  typedef length-must-not-be-4-long {
    type string {
      length '1..3 | 5..max' {
        error-message "Must not be 4 characters long";
      }
    }
  }

  uses second:group1;

  augment /integrationtest:listgroup1 {
    container contain {
      leaf leafa {
        type string;
      }
      leaf leafb {
        type uint32;
      }
    }
  }

  leaf underscore_and-hyphen {
    type empty;
  }

  container diff {

    container deletes {
      uses diff-group;
    }

    container adds {
      uses diff-group;
    }

    container modifies {
      uses diff-group;
    }
  }

  container augments {

  }

  augment /integrationtest:augments {
    leaf xxx {
      type string;
    }
  }

  container cli {

    container zzz {
      leaf zoo {
        type string;
      }
      leaf zebra {
        type string;
      }

      leaf zebeedee {
        type string;
      }
    }
    container a {
      leaf apple {
        type string;
      }
    }

    container aaaaa {
      
    }
    container b {
      leaf bed {
        type string;
      }
      leaf bug {
        type string;
      }
    }

    container c {
      presence true;
      leaf cup {
        type string;
      }
    }

    list d {
      key donkey;
      leaf donkey {
        type string;
      }
    }

  }
  container validator {
    container mandatories {
      presence true;

      leaf this-is-mandatory {
        type string;
        mandatory true;
      }
    }
    container strings {
      leaf nolen {
        type string;
      }

      leaf non-quatre {
        description "For some arbritary reason this must not be 4 long. This is seg faulty
        next(yangctx.find_path('/integrationtest:validator/integrationtest:strings/integrationtest:non-quatre')).type().leaf_length_constraints()
        Without the leaf_length_constraints it's ok
        next(yangctx.find_path('/integrationtest:validator/integrationtest:strings/integrationtest:non-quatre')).type()
        !";

        type length-must-not-be-4-long;

      }
      leaf minlen {
        description "This is not segfaulty
      next(yangctx.find_path('/integrationtest:validator/integrationtest:strings/integrationtest:minlen')).type()..leaf_length_constraints()
      !";
        type string {

          length "1..max";
        }
      }
      leaf maxlen {
        type string {
          length "min..4";
        }
      }
      leaf minmaxlen {
        type string {
          length "2..3";
        }
      }
      leaf sillylen {
        type string {
          length "1..3 | 9..11 | 16..32" {
            error-message "BOO!";
          }
        }
      }
      leaf pattern {
        type string {
          pattern "A..?Z";
        }
      }
      leaf patternerror {
        type string {
          pattern "AZ" {
            error-message "It went wrong";
          }
        }
      }
      leaf patternandlengtherror {
        type string {
          pattern "A.+Z" {
            error-message "It went wrong";
          }
          length "2 | 3" {
            error-message "This is actually duplicated up by the regular expression.";
          }
        }
      }
    }

    container types {
      leaf str {
        type string;
      }
      leaf enumeratio {
        type enumeration {
          enum A;
          enum Z;
        }
      }
      leaf void {
        type empty;
      }
      leaf bool {
        type boolean;
      }
      leaf dec_64 {
        type decimal64 {
          fraction-digits 3;
        }
      }
      leaf int_8 {
        type int8;
      }
      leaf int_16 {
        type int16;
      }
      leaf int_32 {
        type int32;
      }
      leaf int_64 {
        type int64;
      }
      leaf u_int_8 {
        type uint8;
      }
      leaf u_int_16 {
        type uint16;
      }
      leaf u_int_32 {
        type uint32;
      }
      leaf u_int_64 {
        type uint64;
      }
      container present {
        presence true;
      }
      list collection {
        key x;
        leaf x {
          type string;
        }
      }
      leaf-list simplecollection {
        type string;
      }
    }
  }

  container imports-in-here {
    uses testchild:child;
  }

  container web {

    list venues {
      key "name location";

      leaf name {
        type string;
      }

      leaf location {
        type locations;
      }

      leaf country {
        type countries;
        default GB;
      }

      list beers {
        description "Does the venue have any good beer?";
        key name;

        leaf name {
          type string;
        }
      }

      container information {
        description "Usual venue information";

        list profiles {
          key profile;

          leaf profile {
            type string;
          }

          leaf doors-open {
            type string;
          }
          leaf curfew {
            type string;
          }
        }
      }

    }

    list promoters {
      key name;

      leaf name {
        type string;
      }
    }

    list bands {
      key name;

      leaf name {
        type string;
      }

      leaf genre {
        type string;
      }

      list gigs {
        key "year month day venue location";

        leaf year {
          type uint16 {
            range 1999..2079;
          }
        }

        leaf month {
          type uint8 {
            range 1..12;
          }
        }

        leaf day {
          type uint8 {
            range 1..31;
          }
        }

        leaf venue {
          type leafref {
            path "/integrationtest:web/integrationtest:venues/integrationtest:name";
          }
        }

        leaf location {
          type leafref {
            path "/integrationtest:web/integrationtest:venues[integrationtest:name=current()/../integrationtest:venue]/integrationtest:location";
          }
        }

        leaf festival {
          type string;
        }

        container missed {
          presence true;
          leaf reason {
            type string;
          }
        }
        leaf comments {
          type string;
        }

        leaf rating {
          type uint8 {
            range 1..10;
          }
        }

        list support {
          key name;

          leaf name {
            type leafref {
              path "/integrationtest:web/integrationtest:bands/integrationtest:name";
            }
          }

          leaf order {
            type enumeration {
              enum "First Support";
              enum "Second Support";
              enum "Third Support";
              enum "Fourth Support";
            }
          }
        }
      }


    }

    leaf favourite {
      type leafref {
        path "../bands/name";
      }
    }
  }

  container underscoretests {
    crux:info "underscores help text for the container";

    leaf underscore_only {
      type string;
      crux:info "underscores help text";
    }
    leaf hyphen-only {
      type string;
    }
    leaf underscore_and-hyphen {
      type string;
      description "NOW SUPPORTED!!!";
    }
    container deeper_down-here {
      leaf simple {
        type string;
      }
    }
  }

  leaf empty {
    type empty;
  }

  leaf simpleleaf{
    type string;
  }

  leaf dirty-secret {
    type string;
    crux:hide true;
  }

  leaf default {
    type string;
    integrationtest:hide true;
    default "statusquo";
  }

  container whencontainer {
    leaf then {
      type string;
      default "thendefault";
    }
    when "../default='statusquo'";
  }

  leaf thing-that-is-lit-up-for-C {
    type string;
    when "../thing-that-is-used-for-when='C'";
  }

  leaf thing-that-is-lit-up-for-B {
    type string;
    when "../thing-that-is-used-for-when='B'";
  }

  leaf thing-that-is-lit-up-for-A {
    type string;
    when "../thing-that-is-used-for-when='A'";
  }

  leaf thing-that-is-used-for-when {
    type enumeration {
      enum A;
      enum B;
      enum C;
    }
  }

  leaf thing-to-leafref-against {
    type string;
  }

  list list-to-leafref-against {
    key idle;

    leaf idle {
      type string;
    }

    leaf wild {
      type string;
    }
  }

  leaf thing-that-is-a-list-based-leafref {
    crux:info "Should be constratined to the leaf ref";
    description "We won't support crazy expressions, just somewhere to influence the CLI";
    type leafref {
      path "../list-to-leafref-against/wild";
    }
  }

  leaf thing-that-is-leafref {
    crux:info "Should be constratined to the leaf ref";
    description "We won't support crazy expressions, just somewhere to influence the CLI";
    type leafref {
      path "../thing-to-leafref-against";
    }
  }

  grouping unused-grouping {
    leaf unused-grouping-leaf {
      type string;
    }
  }

  container quad {
    container leafinquad {
      presence true;
    }
  }
  container quarter {
    container leafinquarter {
      presence true;
    }
  }

  container container1 {
    presence true;
    leaf leaf1 {
      type string;
    }
    container container2 {
      presence true;
      leaf leaf2a {
        type string;
      }
      leaf leaf2b {
        type string;
      }
      container container3 {
        presence true;
        leaf leaf3 {
          type string;
        }
      }
    }
  }
  container bronze {
    description "The metallics are used to test container nesting";
    uses scale:lots-of-leaves;
    container silver {
      description "Silver is the second level";
      uses scale:lots-of-leaves;
      container gold {
        description "Gold is a bit better than silver";
        uses scale:lots-of-leaves;
        container platinum {
          description "Then we get platinum which is as deep as we go.";
          uses scale:lots-of-leaves;
          leaf deep {
            type string;
          }
          container deeper {
            presence true;
            uses scale:lots-of-leaves;
            leaf gone-too-far {
              type string;
            }
          }
        }
      }
    }
  }
  container psychedelia {
    description "This lets us tests lists, and must conditions";
    list bands {
      key band;
      leaf band {
        type string;
      }
      leaf favourite {
        type boolean;
      }
    }
    container psychedelic-rock {
      list bands {
        key band;
        leaf band {
          type string;
        }
        leaf favourite {
          type boolean;
        }
      }
      container stoner-rock {
        list bands {
          key band;
          leaf band {
            type string;
          }
          leaf favourite {
            type boolean;
          }
          list albums {
            key album;

            leaf album {
              type string;
            }
          }
        }
        must "count(current()/bands[favourite='true'])<2";
      }
      container noise-pop {
        list bands {
          key band;
          leaf band {
            type string;
          }
          leaf favourite {
            type boolean;
          }
        }

        container dream-pop {
          list bands {
            key band;
            leaf band {
              type string;
            }
            leaf favourite {
              type boolean;
            }
          }

        }
        container shoe-gaze {
          list bands {
            key band;
            leaf band {
              type string;
            }
            leaf favourite {
              type boolean;
            }
          }
        }
      }
    }
  }

  list twokeylist {
    key "primary secondary";

    leaf primary {
      type boolean;
    }
    leaf secondary {
      type boolean;
    }
    leaf tertiary {
      type boolean;
    }
  }

  container simplecontainer {
    presence true;
  }

  leaf simpleenum {
    type enumeration {
      enum "A" {
        value 1;
      }
      enum "B" {
        value 2;
      }
    }
  }

  leaf patternstr {
    type string {
      pattern ".*Strasse" {
        error-message "sdfsdf";
      }
    }
  }

  leaf hyphen-leaf {
    type string;
  }

  list outsidelist {
    key "leafo";

    leaf leafo {
      type string;
    }

    list insidelist {
      key "leafi";

      leaf leafi {
        type string;
      }
    }

    list otherinsidelist {
      key "otherlist1 otherlist2 otherlist3";
      leaf otherlist1 {
        type string;
      }

      leaf otherlist2 {
        type string;
      }

      leaf otherlist3 {
        type string;
      }

      leaf otherlist4 {
        type string;
      }

      leaf otherlist5 {
        type string;
      }

      leaf language {
        type enumeration {
          enum french;
          enum german;
          enum dutch;
          enum swedish;
          enum danish;
          enum italian;
          enum spanish;
        }
      }
    }

    leaf other {
      type string;
    }
  }

  container numberlist {
    list integer {
      key k;

      leaf k {
        type uint8;
      }
    }

    list fraction {
      key k;

      leaf k {
        type testchild:temperature;
      }
    }

    list percentage {
      key k;
      leaf k {
        type testchild:percent-dot1;
      }
    }
  }


  container container-and-lists {
    leaf just-a-key {
      type string;
    }
    list lots-of-keys {
      key "A Z Y X B C";
      leaf "C" {
        type string;
      }
      leaf "B" {
        type string;
      }
      leaf "X" {
        type string;
      }
      leaf "A" {
        type string;
      }
      leaf "Z" {
        type string;
      }
      leaf "Y" {
        type string;
      }
    }
    list multi-key-list {
      key "A B";

      leaf "A" {
        type string;
      }
      leaf "B" {
        type string;
      }
      container inner {
        leaf "C" {
          type string;
        }

        list level3list {
          key level3key;
          leaf level3key {
            type string;
          }
          leaf level3-nonkey {
            type string;
          }
        }
      }

      list level2list {
        key level2key;
        leaf level2key {
          type string;
        }
      }
    }

    list numberkey-list {
      key numberkey;

      leaf numberkey {
        type uint8;
      }

      leaf description {
        type string;
      }
    }
  }
 //pyang -f sample-xml-skeleton --sample-xml-skeleton-annotations --sample-xml-skeleton-defaults integrationtest.yang | grep -v '<!-- # entries: ' | sed -e 's/<!-- # /</' | sed -e 's/<!-- /</' | sed -e 's/\.\. -->/"\/>/' | sed -e 's/: / val="/' | sed -e 's/ -->/"\/>/' | sed -e 's/-->/"\/>/' | xmllint --format - >integrationtest.sample.2.xml
 // this looked attractive as an option - however we already have a better option by inversion recursion
  grouping secondlist {
    list listb {
      key "secondkey thirdkey";
      leaf secondkey {
        type string;
      }
      leaf thirdkey {
        type string;
      }
      leaf nonkey {
        type string;
      }
      // note the next two lines are invisible!
      choice MAKEYOURMINDUP {
        case OPTION1 {
          leaf FIRSTOPTION {
              type string;
              crux:info "choice";
          }
        }
        case OPTION2 {
          leaf SECONDOPTION {
            type string;
          }
        }
      }
      container things {
        leaf thing {
          type string;
        }
        leaf musthave {
          type string;
          mandatory true;
        }
      }
      container nothings {

      }
    }
  }

  list lista {
    key firstkey;
    leaf firstkey {
      type string;
    }
    uses secondlist;
  }
  list simplelist {
    key simplekey;

    leaf simplekey {
      type string;
    }

    leaf nonleafkey {
      type uint32;
      description "ABC";
      crux:info "A non-leaf key";
    }
  }

  typedef type-a {
    type uint32;
  }

  grouping group-a {
    leaf a {
      type string;
    }
  }

  container resolver {
    uses group-a;
    leaf leaf-a {
      type type-a;
    }
  }

  container morecomplex {
    container leaflists {
      leaf-list simple {
        description "
        - values must be unique
        - should support min/max len
        - should support if feature
        ";
        type string;
      }
      leaf-list viatypedef {
        type type3;
      }
    }

    container python-reserved-keywords {
      leaf class {
        type string;
      }
      leaf import {
        type empty;
      }
      list and {
        key "break not-break";
        leaf break {
          type string;
        }
        leaf not-break {
          type string;
        }
      }
      leaf-list global {
        type string;
      }
    }

    leaf superstar {
      type percentile95th;
    }

    leaf percentage {
      type decimal64 {
        fraction-digits 1;
      }
    }

    leaf nonconfig {
      config false;
      crux:info "A non-configuration node";
      type string;
    }

    leaf extraboolean {
      type boolean;
    }

    leaf extraboolean2 {
      type boolean;
      default false;
    }

    leaf extraboolean3 {
      type boolean;
      default true;
    }

    leaf leaf2 {
      crux:info "must be 1 or 0 dont sit on the fence";
      type boolean;
    }

    leaf leaf3 {
      crux:info "Should allow a string starting with brew - but no spaces";
      type type2;
    }

    leaf leaf4 {
      crux:info "Should allow A, B, C or a uint32";
      type type4;
    }

    container inner {
      presence true;

      container siblings {
        leaf a {
          type string;
        }
        leaf b {
          type string;
        }
        leaf c {
          type string;
        }
        leaf d {
          type string;
        }
        leaf e {
          type string;
        }
        leaf f {
          type string;
        }
        leaf g {
          type string;
        }
        leaf h {
          type string;
        }
        leaf i {
          type string;
        }
        leaf j {
          type string;
        }
      }

      leaf brewdog-beer {
        type numstr;
      }

      list beer-styles {
        key beer-style;

        leaf beer-style {
          type enumeration {
            enum saison;
            enum new-england;
          }
        }

        choice beer-choice {
          case new-england-case {
            container hazy-style {
              leaf beer-chosen {
                type string;
              }
              leaf rating {
                type uint8;
              }
              leaf size {
                type enumeration {
                  enum third;
                  enum schooner;
                  enum half;
                  enum pint;
                }
              }
            }
          }
        }

      }

      container classifier-example {
        list rules {
          key id;

          leaf id {
            type uint8;
          }

          leaf protocol {
            type enumeration {
              enum ip;
              enum udp;
              enum tcp;
            }
          }

          container ports {
            when "../protocol!='ip'";
            container source {
              leaf port-type {
                type enumeration {
                  enum "between";
                  enum "equal";
                }
                default "equal";
              }

              leaf port {
                type uint8;
                when "../port-type!='between'";
              }
              leaf start-port {
                type uint8;
                when "../port-type='between'";
              }

              leaf end-port {
                type uint8;
                when "../port-type='between'";
              }
            }
          }
        }
      }

      list brewdog-beers {
        key beer;

        leaf beer {
          type numstr;
        }
      }

      choice beer-type {
        case macro {
          leaf fosters {
            type string;
          }
        }

        case craft {
          leaf brewdog {
            type string;
          }
        }

        case ale {
          leaf adnams {
            type string;
          }
        }
      }
      list list-that-will-stay-empty {
        key akey;

        leaf akey {
          type string;
        }
      }

      leaf leaf5 {
        type string;
        mandatory true;
      }

      leaf leaf6 {
        type string;
        mandatory false;
      }

      leaf leaf7 {
        type string;
        default "this-is-a-default";
      }


      leaf leaf8 {
        type type8;
      }

      leaf-list list5555 {
        type string;
      }

      leaf leaf5555 {
        description "Union with a leaf-ref not supported.";
        type union {
          type string;
          type type5555;
        }
      }



      leaf leaf666 {
        description "Pretty nasty";
        type type6;
      }

      leaf leaf777 {
        description "Leafref to a simple type";
        type leafref {
          path "../leaf7";
        }
      }
      leaf leaf888 {
        description "This might get to the heart of segfaults....
        TYPEDEF888 -> TYPEDEF88
        TYPEDEF88  -> TYPE8
        TYPEDEF8   -> UNINON  { type2          type3               type5
                                  |                |                 |
                                uint32       enum (A.B.C)          string

        ";
        type type8;
      }

      leaf leaf-union-of-union {
        type union {
          type union {
            type string;
            type uint32;
          }
          type decimal64 {
            fraction-digits 2;
          }
        }
      }
      leaf leaf888-withoutenum {
        description "This might get to the heart of segfaults...

        TYPEDEF888 -> TYPEDEF88
        TYPEDEF88  -> TYPE8
        TYPEDEF8-noenum-> UNINON  { type2            type5
                                      |               |
                                    uint32           string

        Two theories (perhaps three)
        a) leafrefs
        b) enums
        c) something else";
        type type8-noenum;
      }

      leaf leaf8888 {
        description "Leafref to the complex stuff";
        type leafref {
          path "../leaf666";
        }
      }

      leaf leaf999 {
        description "Leafref to a simple type of boolean";
        type leafref {
          path "../../leaf2";
        }
      }

      leaf leaf000 {
        description "Numbers";
        type sillytypedef;
      }

      leaf leaf111 {
        description "Union without typedefs";
        type union {
          type enumeration {
            enum cow;
            enum pig;
            enum sheep;
          }
          type string;
          type uint32;
          type boolean;
        }
      }

      leaf leaf112 {
        type union {
          type enumeration {
            enum vocation;
          }
          type uint32;
        }
      }

      leaf leaf113 {
        type union {
          type enumeration {
            enum vocation;
          }
          type uint32;
          type boolean;
        }
      }


      container ietf-inet-types {

        container ip {
          leaf address {
            type inet:ip-address;
          }
        }
      }

    }
  }

  typedef type1 {
    type string {
      pattern "brew[a-z]*" {
        error-message "String must start with brew";
      }
    }
  }

  typedef type2 {
    type uint32;
  }

  typedef type3 {
    type enumeration {
      enum A;
      enum B;
      enum C;
    }
  }

  typedef type4 {
    type union {
      type type3;
      type type2;
    }
  }

  typedef type5 {
    type string;
  }

  typedef type6 {
    description "Complex maaping which ultimately allows a string (type5) or a uin32 (type2 via type4)
    or an enumeration A B C (type 3 via type4) or 1, '3', '5' via type7";
    type union {
      type type4;
      type type5;
      type type7;
    }
  }

  typedef type7 {
    type enumeration {
      enum 1;
      enum "3";
      enum "5";
    }
  }

  typedef type8 {
    description "This union captures what is currently supported.... type6 is viewed as corner case.
    Although this is actually not handldewd (libyang-ciffg) or segfaulty (yang native bindingG)";
    type union {
      type type2;
      type type3;
      type type5;
    }
  }

  typedef type8-noenum {
    description "Same as type8 without the enum";
    type union {
      type type2;
      type type5;
    }
  }
  typedef typeu8 {
    type uint8;
  }

  typedef typeu16 {
    type uint16;
  }

  typedef typeu32 {
    type uint32;
  }

  typedef typeu64 {
    type uint64;
  }

  typedef typei8 {
    type int8;
  }

  typedef typei16 {
    type int16;
  }

  typedef typei32 {
    type int32;
  }

  typedef typei64 {
    type int64;
  }

  typedef sillytypedef {
    type union {
      type typeu8;
      type typeu16;
      type typeu32;
      type typeu64;
      type typei8;
      type typei16;
      type typei32;
      type typei64;
    }
  }

  typedef percentile95th {
    type decimal64 {
      fraction-digits 1;
      range 95..100;
    }
  }

  typedef type88 {
    type type8;
  }

  typedef type888 {
    type type88;
  }

  typedef numstr {
    type union {
      type uint8 {
        range 1..5;
      }
      type enumeration {
        enum albion-squid-assassin;
        enum black-hammer;
        enum cloud-cartel;
        enum death-or-glory;
        enum eight-bit;
      }
    }
  }
  grouping diff-group {
    leaf a-leaf {
      type string;
    }
    leaf a-2nd-leaf {
      type string;
    }
    leaf empty-leaf {
      type empty;
    }
    leaf boolean {
      type boolean;
    }
    list a-list {
      key listkey;

      leaf listkey {
        type string;
      }

      leaf listnonkey {
        type string;
      }
    }

    leaf-list a-leaf-list {
      type string;
    }

    container presence-container {
      presence true;
    }
  }

  container scaling {
      uses scale:thirty-lists;

  }

  typedef type5555 {
    type leafref {
      path "/integrationtest:morecomplex/integrationtest:inner/integrationtest:list5555";
    }
  }
}
